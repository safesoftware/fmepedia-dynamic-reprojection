FME workspace reprojection_demo.fmw

Parameters:
- XVALATTR = 50.141237   # X Value
- YVALATTR = 7.294922   # Y Value
- COORDSYS = NA-LM-CONIC

Writers:
- GEOJSON_1: GEOJSON to C:\Users\sharper\Desktop\output.json

Creator
    NUM = 1
    GEOMTYPE = Geometry Object
    CREATED -> PointCreator
Note: Creates a point. The X,Y parameters are both published / and when you run a job it is these values we pass in.
PointCreator: 3DPointReplacer
    XVALATTR = $(XVALATTR)
    ZVALATTR = 0
    YVALATTR = $(YVALATTR)
    POINT -> CoordinateSystemSetter
CoordinateSystemSetter
    COORDSYS = EPSG:4326
    -> Reprojector
Note: Reprojects the point to the requested / coordinate system.
Reprojector
    DEST = $(COORDSYS)
    RASTER_CELL_SIZE = Preserve Cells
    STROKE_ARCS = Yes
    SOURCE = Read from feature
    INTERPOLATION_TYPE_NAME = Nearest Neighbor
    REPROJECTED -> ParameterFetcher
ParameterFetcher
    ATTR_LIST = CoordinateSys {$(COORDSYS)}
    -> Output (writer GEOJSON_1)
Output (writer GEOJSON_1)
    attributes: CoordinateSys string
